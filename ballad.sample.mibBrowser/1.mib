PHOTON-GLOBAL-REG DEFINITIONS ::= BEGIN

IMPORTS
    OBJECT-IDENTITY,
    MODULE-IDENTITY,
    enterprises
		FROM SNMPv2-SMI
    ;



photonGlobalRegModule MODULE-IDENTITY
    LAST-UPDATED "0202060000Z"
    ORGANIZATION "Photonic Bridges"
    CONTACT-INFO "Photonic Bridges
                  19500 Pruneridge Ave #3206
                  Cupertino, CA 95014"
    DESCRIPTION  "This module defines the OID infrastructure and other registrations"
    REVISION     "0202060000Z"
    DESCRIPTION  "Initial version"
    ::= { photonModules 1 }

photonicBridgesRoot    OBJECT IDENTIFIER
        ::= { enterprises 12505 }

metroWaveRoot       OBJECT IDENTIFIER
        ::= { photonicBridgesRoot 1 }

--

photonReg      OBJECT-IDENTITY
        STATUS          current
        DESCRIPTION     "Sub-tree for registrations"
        ::= { metroWaveRoot 1 }

photonGeneric  OBJECT-IDENTITY
        STATUS          current
        DESCRIPTION     "Sub-tree for common object and event definitions"
        ::= { metroWaveRoot 2 }

photonProducts OBJECT-IDENTITY
        STATUS          current
        DESCRIPTION     "Sub-tree for specific object and event definitions"
        ::= { metroWaveRoot 3 }

photonCaps     OBJECT-IDENTITY
        STATUS          current
        DESCRIPTION     "Sub-tree for agent profiles"
        ::= { metroWaveRoot 4 }

photonReqs     OBJECT-IDENTITY
        STATUS          current
        DESCRIPTION     "Sub-tree for management application requirements"
        ::= { metroWaveRoot 5 }

photonExpr     OBJECT-IDENTITY
        STATUS          current
        DESCRIPTION     "Sub-tree for experimental definitions"
        ::= { metroWaveRoot 6 }

--
-- Registrations
--

photonModules          OBJECT-IDENTITY
        STATUS          current
        DESCRIPTION     "Sub-tree for module registrations"
        ::= { photonReg 1 }

photonNetworkingProducts OBJECT-IDENTITY
        STATUS          current
        DESCRIPTION     "Sub-tree for networking product registrations"
        ::= { photonReg 2 }

metrowaveReg            OBJECT-IDENTITY
        STATUS          current
        DESCRIPTION     "MW863"
        ::= { photonNetworkingProducts 1 }

--
-- Products
--

photonMetroWaveProducts  OBJECT-IDENTITY
        STATUS          current
        DESCRIPTION     "Sub-tree for the metro wave product line"
        ::= { photonProducts 1 }

photonMetroWaveCommon    OBJECT-IDENTITY
        STATUS          current
        DESCRIPTION     "Definitions common to the metro wave products"
        ::= { photonMetroWaveProducts 1 }

END
